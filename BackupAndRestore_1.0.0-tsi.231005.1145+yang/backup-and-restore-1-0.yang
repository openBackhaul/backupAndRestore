module backup-and-restore-1-0 {
  yang-version 1.1;
  namespace "urn:onf:yang:backup-and-restore-1-0";
  prefix backup-and-restore;

  import core-model-1-4 {
    prefix core-model;
  }

  organization
    "openBackhaul.com proposal to Open Networking Foundation (ONF)";
  contact
    "WG Web : https://github.com/openBackhaul/Overview
     WG List: backupAndRestore@openBackhaul.com
     Editor : Thorsten Heinze
     Email  : Thorsten.Heinze@openBackhaul.com";
  description
    "Augment to the ControlConstruct for managing firmware on the device.

     Copyright 2023 openBackhaul.com

     Licensed under the Apache License, Version 2.0 (the 'License');
     you may not use this file except in compliance with the License.
     You may obtain a copy of the License at
     http://www.apache.org/licenses/LICENSE-2.0
     Unless required by applicable law or agreed to in writing, software
     distributed under the License is distributed on an 'AS IS' BASIS,
     WITHOUT WARRANTIES OR CONDITIONS OF ANY KIND, either express or implied.
     See the License for the specific language governing permissions and
     limitations under the License.";

  revision 2023-10-05 {
    description
      "Model for the Transport SDN Introduction at Telefonica.
       Please view https://github.com/openBackhaul/backupAndRestore/issues for changes.";
    reference
      "https://github.com/openBackhaul/backupAndRestore/tree/tsi: Model definition
       https://github.com/openBackhaul/onfCoreIm/tree/tsi: ONF TR-512 Core IM incl. Profile and enhanced Equipment definition";
  }
  revision 2022-03-29 {
    description
      "Model for the Transport SDN Introduction at Telefonica.
       Please view https://github.com/openBackhaul/backupAndRestore/issues for changes.";
    reference
      "https://github.com/openBackhaul/backupAndRestore/tree/tsi: Model definition
       https://github.com/openBackhaul/onfCoreIm/tree/tsi: ONF TR-512 Core IM incl. Profile and enhanced Equipment definition";
  }

  augment "/core-model:control-construct" {
    uses backup-and-restore-cc-spec;
    description
      "none";
  }

  /****************************************
   * grouping statements for object classes
   **************************************/ 

  grouping backup-and-restore-cc-spec {
    container backup-and-restore-pac {
      uses backup-and-restore-pac;
      description
        "none";
    }
    description
      "none";
  }

  grouping backup-and-restore-pac {
    container backup-and-restore-capability {
      config false;
      uses backup-and-restore-capability;
      description
        "none";
    }
    container backup-and-restore-configuration {
      uses backup-and-restore-configuration;
      description
        "none";
    }
    container backup-and-restore-status {
      config false;
      uses backup-and-restore-status;
      description
        "none";
    }
    description
      "none";
  }

  grouping backup-and-restore-capability {
    leaf separate-activation-is-required {
      type boolean;
      default "false";
      config false;
      description
        "True = Device requires calling applyRestoredConfiguration operation for activating the configuration, which has been loaded on the device by calling restoreSystem operation before. False = restoreSystem operation includes automatically restarting and activating the restored configuration.";
    }
    leaf confirm-restoration-is-required {
      type boolean;
      default "false";
      config false;
      description
        "True = calling the confirmRestoration RPC within the confirmation period is required for preventing the system to perform a roll-back of the restoration.";
    }
    description
      "none";
  }

  grouping backup-and-restore-configuration {
    leaf length-of-confirmation-period {
      type int16;
      units "s";
      default "-1";
      description
        "Period of time, in which the confirmRestoration() operation has to called for confirming successful establishing of a management connection and preventing the device to roll-back the restore operation.";
    }
    leaf length-of-validation-period {
      type int16;
      units "s";
      default "-1";
      description
        "If backup configuration could not be restored, roll-back to former configuration shall be initiated until latest end of validationPeriod [s]. The value of lengthOfValidationPeriod needs to be smaller than the value of the lengthOfConfirmationPeriod.";
    }
    description
      "none";
  }

  grouping backup-and-restore-status {
    leaf backup-operation-status {
      type backup-status-type;
      default "BACKUP_STATUS_TYPE_NOT_YET_DEFINED";
      config false;
      description
        "Operational status of the firmware.";
    }
    leaf restore-operation-status {
      type restore-status-type;
      default "RESTORE_STATUS_TYPE_NOT_YET_DEFINED";
      config false;
      description
        "Operational status of the firmware.";
    }
    leaf ready-for-starting-new-operation {
      type readiness-status-type;
      default "READINESS_STATUS_TYPE_NOT_YET_DEFINED";
      config false;
      description
        "Implementations are representing different status values at the end of the backup operation. This attribute shall harmonize indicating availability for starting a new backup operation.";
    }
    description
      "none";
  }

  /****************************************
   * typedef statements
   **************************************/ 

  typedef backup-status-type {
    type identityref {
      base BACKUP_STATUS_TYPE;
    }
    description
      "none";
  }

  typedef restore-status-type {
    type identityref {
      base RESTORE_STATUS_TYPE;
    }
    description
      "none";
  }

  typedef readiness-status-type {
    type identityref {
      base READINESS_STATUS_TYPE;
    }
    description
      "none";
  }

  /*********************************************
   * grouping statements for complex data types
   *******************************************/ 

  identity BACKUP_STATUS_TYPE {
    description
      "none";
  }

  identity BACKUP_STATUS_TYPE_IDLE {
    base BACKUP_STATUS_TYPE;
    description
      "Status value to be represented whenever no operation is on-going.";
  }

  identity BACKUP_STATUS_TYPE_ONGOING {
    base BACKUP_STATUS_TYPE;
    description
      "none";
  }

  identity BACKUP_STATUS_TYPE_COMPLETED {
    base BACKUP_STATUS_TYPE;
    description
      "none";
  }

  identity BACKUP_STATUS_TYPE_FAILED {
    base BACKUP_STATUS_TYPE;
    description
      "none";
  }

  identity BACKUP_STATUS_TYPE_ABORTING {
    base BACKUP_STATUS_TYPE;
    description
      "none";
  }

  identity BACKUP_STATUS_TYPE_NOT_YET_DEFINED {
    base BACKUP_STATUS_TYPE;
    description
      "none";
  }

  identity RESTORE_STATUS_TYPE {
    description
      "none";
  }

  identity RESTORE_STATUS_TYPE_IDLE {
    base RESTORE_STATUS_TYPE;
    description
      "Status value to be represented whenever no restore operation is on-going.";
  }

  identity RESTORE_STATUS_TYPE_DOWNLOADING {
    base RESTORE_STATUS_TYPE;
    description
      "Indicates that the device could successfully start the download.";
  }

  identity RESTORE_STATUS_TYPE_DOWNLOADED {
    base RESTORE_STATUS_TYPE;
    description
      "After successfully downloading and verifying the configuration file, but before activating the downloaded configuration.";
  }

  identity RESTORE_STATUS_TYPE_RESTARTING {
    base RESTORE_STATUS_TYPE;
    description
      "none";
  }

  identity RESTORE_STATUS_TYPE_WAITING_FOR_CONFIRMATION {
    base RESTORE_STATUS_TYPE;
    description
      "After restarting with the restored configuration, the device is waiting for the confirmRestoration() operation being called as a confirmation for an existing management connection. If no call of the confirmRestoration() operation has been received before end of confirmation period, the device will automatically roll-back into its former configuration.";
  }

  identity RESTORE_STATUS_TYPE_COMPLETED {
    base RESTORE_STATUS_TYPE;
    description
      "After successfully activating the downloaded configuration and receiving the call of the confirmRestoration() operation (if supported by the device).";
  }

  identity RESTORE_STATUS_TYPE_FAILED {
    base RESTORE_STATUS_TYPE;
    description
      "Potential reasons for representing this status value are: device could not authenticate at the SFTP server, file could not be found, file content could not successfully be validated, operation failed for any other reason.";
  }

  identity RESTORE_STATUS_TYPE_ABORTING {
    base RESTORE_STATUS_TYPE;
    description
      "After abortRestoreOperation() operation has been called.";
  }

  identity RESTORE_STATUS_TYPE_NOT_YET_DEFINED {
    base RESTORE_STATUS_TYPE;
    description
      "This value to be represented, if the device does not support this status attribute.";
  }

  identity READINESS_STATUS_TYPE {
    description
      "none";
  }

  identity READINESS_STATUS_TYPE_READY {
    base READINESS_STATUS_TYPE;
    description
      "none";
  }

  identity READINESS_STATUS_TYPE_NOT_READY {
    base READINESS_STATUS_TYPE;
    description
      "none";
  }

  identity READINESS_STATUS_TYPE_NOT_YET_DEFINED {
    base READINESS_STATUS_TYPE;
    description
      "none";
  }

  /****************************************
   * package interfaces
   **************************************/ 

  rpc backup-system {
    description
      "Operation for creating and uploading a backup file that contains configuration of interfaces, users and system level configurations.";
    input {
      leaf filename {
        type string;
        mandatory true;
        description
          "Name of the file that is to be created and uploaded towards the SFTP server.";
      }
      leaf destination-uri {
        type string;
        mandatory true;
        description
          "URI specifying the remote-file-path for uploading the backup file. Format:<protocol>://<host>[:port]/path'.";
      }
      leaf username-at-file-server {
        type string;
        description
          "Username to access the file server.";
      }
      leaf password-at-file-server {
        type string;
        description
          "Password to access the file server.";
      }
      leaf ssh-key {
        type string;
        description
          "Client key for accessing the file server.";
      }
      leaf force-upload {
        type boolean;
        mandatory true;
        description
          "File to be overwritten in case already existing on the destination file system.";
      }
    }
  }

  rpc restore-system {
    description
      "Operation for downloading and restoring the configuration that is saved in a backup file. In case the device could not successfully validate the downloaded configuration before validationPeriod has passed, the system shall automatically abort the restoreSystem operation. In case the device would not receive a call on the confirmRestoration operation by the management system after successfully executing the restoreOperation, the system shall automatically initiate the rollBack operation.";
    input {
      leaf filename {
        type string;
        mandatory true;
        description
          "Name of the file, which is to be downloaded.";
      }
      leaf source-uri {
        type string;
        mandatory true;
        description
          "URI specifying the remote-file-path for downloading the backup file. Format:<protocol>://<host>[:port]/path'.";
      }
      leaf username-at-file-server {
        type string;
        description
          "Username to access the file server.";
      }
      leaf password-at-file-server {
        type string;
        description
          "Password to access the file server.";
      }
      leaf ssh-key {
        type string;
        description
          "Client key for accessing the file server.";
      }
    }
  }

  rpc apply-restored-configuration {
    description
      "If (separateActivationIsRequired == true) calling the applyRestoredConfiguration RPC is required for activation of the restored configuration.";
  }

  rpc confirm-restoration {
    description
      "If (confirmRestorationIsRequired == true) calling the confirmRestoration RPC is required for preventing the system to perform a roll-back of the restoration. confirmRestoration operation has to be called to confirm successful execution of the restoreSystem operation (which includes successfully re-establishing the management connection).";
  }

  rpc abort-backup-operation {
    description
      "Currently on-going upload of a backup file shall immediately be terminated.";
  }

  rpc abort-restore-operation {
    description
      "Currently on-going download and restore operation shall immediately be terminated.";
  }

  rpc roll-back-operation {
    description
      "The rollBack operation shall facilitate switching back to the former configuration even after confirming successful exection of the restoreSystem operation.";
  }
}
